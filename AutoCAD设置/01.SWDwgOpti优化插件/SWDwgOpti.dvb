Attribute VB_Name = "SubProgram"
Const PI = 3.14159265
Const EERROR = 0.0001


Public Sub AutoRun()
    ThisDrawing.Preferences.LineWeightDisplay = False
    Call AddHZ
    Call SubProgram.MyDim
    Call SubProgram.MyNote
    Call SubProgram.MyText
    Call SubProgram.mySfSymbol
    Call SubProgram.MyDatum
    ThisDrawing.Regen acAllViewports
End Sub

Public Sub endmsg()
Call myDimStyle
MsgBox "执行完成！"
End Sub


Public Sub LoadLin()
    On Error GoTo ERRORHANDLER

    Dim linFile As String
    linFile = FindFile("Lee.lin")
    
    Dim linetypeNames As Variant

    linetypeNames = Array( _
    "WATER_OIL1", _
    "DRAIN_OIL1", _
    "DRAIN_OIL2", _
    "PRESSURE_OIL1", _
    "STAR_LINE1", _
    "STAR_LINE2", _
    "STAR_LINE3", _
    "STAR_LINE4", _
    "AST_OIL1", _
    "AST_OIL2", _
    "OPC_OIL1", _
    "OPC_OIL2", _
    "OPC_OIL3", _
    "OPC_OIL4", _
    "BOX_LINE1" _
    )
    
    Index = False
    For Each Entry In ThisDrawing.textStyles
        If Entry.Name = "HZ" Then
            Index = True
            Exit For
        End If
    Next Entry
    
    If Not Index Then
        Call AddHZ
    End If
        
    For Each lin In linetypeNames
        ThisDrawing.Linetypes.Load lin, linFile
    Next lin
    
    Exit Sub
    
ERRORHANDLER:
    MsgBox Err.Description

End Sub

'------------------------------------------------------------------------------------------------------------------------------------------------------
'------------------------------------------------------------------------------------------------------------------------------------------------------
'将SW工程图转换的DWG图纸的公差用文字替代方式替代
'By Lee
'v1.4 2013-04-10
Public Sub MyDim()
    On Error Resume Next
    Call myDimStyle
    Dim dimset As AcadSelectionSet
    Dim Entry As Variant
    Dim tt As Double

    Dim DimLayer As AcadLayer
    Set DimLayer = ThisDrawing.Layers.Add("Dim")
    With DimLayer
        .Linetype = "CONTINUOUS"
        .color = acRed
        .Lineweight = acLnWtByLwDefault
    End With

    Set dimset = CtSS("Dimset")

    Dim Filtertype(0 To 3) As Integer, Filterdata As Variant
    Filtertype(0) = -4: Filtertype(1) = 0: Filtertype(2) = 0: Filtertype(3) = -4
    Filterdata = Array("<OR", "Dimension", "Tolerance", "OR>")
    ThisDrawing.Utility.Prompt vbCr & "选择标注："
    dimset.SelectOnScreen Filtertype, Filterdata

    Dim sUpper As String, sLower As String
    Dim iType As Integer
    Dim sDimtext As String
    Dim sPositive As String, sMinus As String
    Dim myGBDim As AcadDimStyle
    Set myGBDim = ThisDrawing.ActiveDimStyle

    For Each Entry In dimset
'        Debug.Print Entry.ObjectName
        If Entry.ObjectName = "AcDbFcf" Then GoTo TOLERANCE  '是形位公差则跳转
    
        sDimtext = Entry.TextOverride

        If Right(sDimtext, 2) = "\P" Then sDimtext = Replace(sDimtext, "\P", "", Len(sDimtext) - 2, 1)
        iType = Entry.ToleranceDisplay
        If iType <> 0 Then
            sUpper = Entry.ToleranceUpperLimit
            sLower = Entry.ToleranceLowerLimit


            If Entry.TextOverride = "" Then
                sDimtext = "<>"
            Else
                sDimtext = Entry.TextOverride
            End If
        
            Select Case iType
            Case 1  '对称公差
                If sUpper <> CInt(sUpper) Then sUpper = Format(sUpper, "##0.####")
                sDimtext = Replace(sDimtext, "<>", "<>" & "%%P" & sUpper)
            Case 2  '极限偏差
                If Not (sUpper > 0) Then
                    sPositive = ""
                Else
                    sPositive = "+"
                End If
                If sLower < 0 Then
                    sMinus = "+"
                    sLower = Abs(sLower)
                ElseIf sLower > 0 Then
                    sMinus = "-"
                Else
                    sMinus = ""
                End If
            
                If sUpper <> CInt(sUpper) Then
                    sUpper = Format(sUpper, "##0.####")
                End If
                If sLower <> CInt(sLower) Then
                    sLower = Format(sLower, "##0.####")
                End If
                sDimtext = Replace(sDimtext, "<>", "<>{\H0.6x;\A1;\S" & sPositive & sUpper & "^" & sMinus & sLower & ";}")
            End Select
            Entry.ToleranceDisplay = 0
            Entry.TextOverride = sDimtext
        End If
        
        If InStr(Entry.TextOverride, "M<>") > 0 And Entry.ObjectName = "AcDbDiametricDimension" Then '直径样式的螺纹标注将直径替换为仅数值
            Entry.StyleName = myGBDim.Name & "$3"
            tt = Entry.Measurement
            If Abs(tt - Int(tt)) > EERROR Then tt = Format(tt, "##0.####") Else tt = Int(tt)
            Entry.TextOverride = Replace(Entry.TextOverride, "<>", tt)
        End If
    
TOLERANCE:                          '设置所有标注为当前激活的标注样式
        Select Case Entry.ObjectName
        Case "AcDbDiametricDimension"
            Entry.StyleName = myGBDim.Name & "$3"
        Case "AcDbRadialDimension"
            Entry.StyleName = myGBDim.Name & "$4"
        Case "AcDb2LineAngularDimension"
            Entry.StyleName = myGBDim.Name & "$2"
        Case Else
            Entry.StyleName = myGBDim.Name
        End Select
        
    With Entry
        .Layer = "Dim"
        .color = acByLayer
        .Linetype = "BYLAYER"
        .Lineweight = acLnWtByLayer
    End With
    Entry.Update
    Next Entry
End Sub
'------------------------------------------------------------------------------------------------------------------------------------------------------
'------------------------------------------------------------------------------------------------------------------------------------------------------
'将SW工程图转换的DWG图纸的技术要求块中文字转化成多行文字
'暂不能转化公差
'By Lee
'v1.0 2011-05-16
Public Sub MyNote()
On Error Resume Next
Call AddHZ
Dim swNote As Object
Dim mySet As AcadSelectionSet
Dim myNote0 As AcadMText
Dim myInpoint(0 To 2) As Double
Dim myNotewidth As Double
Dim sNote As String
Dim sNoteentry As Variant
Dim pInpoint1 As Variant
Dim pInpoint2 As Variant
Dim element As Object

Set mySet = CtSS("mySet")

Dim Filtertype(0) As Integer, Filterdata(0) As Variant
Filtertype(0) = 0
Filterdata(0) = "Insert"
ThisDrawing.Utility.Prompt vbCr & "选择技术要求块："
mySet.SelectOnScreen Filtertype, Filterdata

ii = 0
i = 0
'Dim removeItem() As AcadEntity: ReDim removeItem(0 To mySet.Count) As AcadEntity
For Each Entry In mySet
    If InStr(Entry.Name, "SW_NOTE") > 0 Then
        Entry.GetBoundingBox pInpoint1, pInpoint2
        myInpoint(0) = pInpoint1(0): myInpoint(1) = pInpoint2(1)
        myNotewidth = CInt(pInpoint2(0) - pInpoint1(0))
        sNoteentry = Entry.Explode
        Entry.Erase
        ii = 1
        Exit For
'    Else
'        Set removeItem(i) = entry '不是技术要求的块，移除
'        i = i + 1
    End If
Next Entry
'mySet.RemoveItems removeItem
If ii = 0 Then '没有选择技术要求报错
'MsgBox ("请选择技术要求所在块！")
'End
GoTo noNote
End If

sNote = ""
kk = UBound(sNoteentry)
For i = 0 To UBound(sNoteentry)
'    sNote = sNote & "\H" & CStr(sNoteentry(i).Height) & ";" & sNoteentry(i).TextString
    If i = 0 Then
        sNote = "\H7;" & sNote & sNoteentry(i).textString
    Else: sNote = sNote & "\H5;" & sNoteentry(i).textString
    End If
'    MsgBox sNoteentry(i).ObjectName & sNoteentry(i).ObjectID
    If StrComp(sNoteentry(i).ObjectName, "AcDbMText") = 0 Then
        pInpoint1 = sNoteentry(i).InsertionPoint
        For j = i + 1 To UBound(sNoteentry)
            pInpoint2 = sNoteentry(j).InsertionPoint
            Set element = sNoteentry(i)
            N = element.Height: Max = pInpoint1(1) + N: Min = pInpoint1(1) - N
            If pInpoint2(1) < Max And pInpoint2(1) > Min Then
'            sNote = sNote & "\H" & CStr(sNoteentry(i).Height) & ";" & sNoteentry(j).TextString
            sNote = sNote & sNoteentry(j).textString
            i = j
            Else
'            sNote = sNote & "\H" & CStr(sNoteentry(i).Height) & ";" & sNoteentry(i).TextString
            Exit For
            End If
        Next j
        sNote = sNote & "\P"
    End If
Next i
For i = 0 To UBound(sNoteentry)
sNoteentry(i).Delete
Next i
'Φ

Set myNote0 = ThisDrawing.ModelSpace.AddMText(myInpoint, myNotewidth, sNote)
With myNote0
'    .AttachmentPoint = acAttachmentPointBottomLeft
    .StyleName = "HZ"
    .Layer = "TXT"
    .Linetype = "BYLAYER"
    .TrueColor.ColorIndex = acByLayer
End With
noNote: mySet.Delete
End Sub

'------------------------------------------------------------------------------------------------------------------------------------------------------
'------------------------------------------------------------------------------------------------------------------------------------------------------
'添加HZ字体样式
'
'By Lee
'v1.0 2011-05-16
Public Sub AddHZ()
On Error Resume Next
Dim myTxtstyle As AcadTextStyles
Dim HZ As AcadTextStyle
'
'ii = 0
'For Each Entry In ThisDrawing.textStyles
'    If Entry.Name = "HZ" Then
'        ii = 1: Exit For
'    End If
'    If ii = 0 Then
        Set HZ = ThisDrawing.textStyles.Add("HZ")
'    End If
'Next Entry
With HZ
    .fontFile = "txt"
    .BigFontFile = "hztxt"
    .Height = 0
    .Width = 0.667
    .ObliqueAngle = 0
End With
ThisDrawing.ActiveTextStyle = HZ
ThisDrawing.Regen acActiveViewport
End Sub

''------------------------------------------------------------------------------------------------------------------------------------------------------
''------------------------------------------------------------------------------------------------------------------------------------------------------
''修改粗糙度标注,调整文字位置
''
''By Lee
''v1.0 2011-05-17
Sub mySfSymbol()
    On Error Resume Next
    Dim sEntry As AcadBlock
    Dim lLine As AcadEntity
    Dim length As Double: length = 0
    Dim myLine As AcadLine
    Dim inCen(0 To 2) As Double
    Dim Mtxt As AcadMText
    Dim x0 As Double, x1 As Double, y0 As Double, y1 As Double, an As Double
    Dim stPt As Variant
    Dim oldCen(0 To 2) As Double
    Const PI As Double = 3.14159265358979
    Const deltaAn As Double = 61.074 / 180 * PI / 2
    Const myLen = 7.5
    Dim ii As Integer
    Dim pCC(0 To 2) As Double
    
    For Each Entry In ThisDrawing.Blocks
'    粗糙度标注
    i = 0: length = 0
    If InStr(Entry.Name, "SW_SFSYMBOL") > 0 Then
        For Each element In Entry
            If element.ObjectName = "AcDbLine" Then
                element.color = acByLayer
                element.Layer = "ECOY"
'                If element.length > length Then
                If element.length > 11.6 And element.length < 11.62 Then  '选取长边线，尽量排除引线干扰
                    Set lLine = element
                    length = lLine.length
                End If
            ElseIf element.ObjectName = "AcDbMText" Then
                element.color = acGreen
                Set Mtxt = element
                ii = 1
            End If
        Next element

        If ii > 0 Then
            stPt = lLine.StartPoint
            x0 = stPt(0): y0 = stPt(1)
            an = lLine.Angle + deltaAn
            x1 = x0 + myLen * Cos(an): y1 = y0 + myLen * Sin(an)
            inCen(0) = x1: inCen(1) = y1: inCen(2) = 0
'            Call Entry.AddCircle(inCen, 1)
            Mtxt.AttachmentPoint = acAttachmentPointMiddleCenter
            stPt = Mtxt.InsertionPoint
            oldCen(0) = stPt(0): oldCen(1) = stPt(1): oldCen(2) = stPt(2)
            Mtxt.Move oldCen, inCen
        End If
    End If
    Next Entry
    
    ThisDrawing.Regen acAllViewports
End Sub

'------------------------------------------------------------------------------------------------------------------------------------------------------
'------------------------------------------------------------------------------------------------------------------------------------------------------
'修改所有文字和多行文字为HZ样式，修改所有字体样式为hztxt大字体样式
'
'By Lee
'v1.0 2011-05-17
Public Sub MyText()
On Error Resume Next
Call AddHZ

For Each Entry In ThisDrawing.ModelSpace
    If Entry.ObjectName = "AcDbText" Or Entry.ObjectName = "AcDbMText" Then
        Entry.StyleName = "HZ"
        Entry.Layer = "TXT"
        Entry.Linetype = "BYLAYER"
        Entry.color = 256
        Entry.Update
    End If
Next Entry
For Each Entry In ThisDrawing.textStyles
    Entry.fontFile = "txt"
    Entry.BigFontFile = "hztxt"
    Entry.Height = 0
'    Entry.Width = 0.667
    Entry.ObliqueAngle = 0
Next Entry
End Sub

'------------------------------------------------------------------------------------------------------------------------------------------------------
'------------------------------------------------------------------------------------------------------------------------------------------------------
'新建国标标注样式
'
'By Lee
'v1.3 2013-04-10
Public Function myDimStyle()
    On Error Resume Next
    'Call AddHZ
       
    Dim dimStyle As AcadDimStyle
    Dim DimRa, DimAn, DimDi, DimLi As AcadDimStyle
    Dim TxtRow() As Variant, ConstName() As String, ConstValue() As String, SplitTxt() As String
    Dim L As Integer: L = -1
    Dim GBConstFileName As String
    Dim dDimLFac As Double: dDimLFac = ThisDrawing.Utility.GetReal("请输入标注比例:<" & dDimLFac & ">")
    Dim DimStyleName As String: DimStyleName = "GBDim" & "X" & dDimLFac
    
    Set dimStyle = ThisDrawing.DimStyles.Add(DimStyleName)
    Set DimRa = ThisDrawing.DimStyles.Add(DimStyleName & "$4")
    Set DimAn = ThisDrawing.DimStyles.Add(DimStyleName & "$2")
    Set DimDi = ThisDrawing.DimStyles.Add(DimStyleName & "$3")
'    Set DimLi = ThisDrawing.DimStyles.Add(DimStyleName & "$5")
    
    GBConstFileName = FindFile("GBDimConst")
    If GBConstFileName = "" Then MsgBox "没有找到GBDimConst文件。请确认已将文件所在目录加入CAD支持的搜索路径。": GoTo EEnd
    Close #1: Open GBConstFileName For Input As #1
    Do Until EOF(1)
    L = L + 1
    ReDim Preserve ConstName(L), ConstValue(L), TxtRow(L)
    Line Input #1, TxtRow(L)
    ConstName(L) = Split(TxtRow(L), ";")(0)
    ConstValue(L) = Split(TxtRow(L), ";")(1)
    If InStr(ConstValue(L), "/*") > 0 Then ConstValue(L) = Split(ConstValue(L), "/*")(0)
    ConstName(L) = Replace(ConstName(L), vbTab, "")
    ConstValue(L) = Replace(ConstValue(L), vbTab, "")
    Loop
    Close #1

    Dim i As Integer, cName As String, cValue As Variant
    For i = 0 To UBound(ConstName)
        cName = CStr(ConstName(i))
        If IsNumeric(ConstValue(i)) Then
            cValue = CDbl(ConstValue(i))
        Else
            cValue = CVar(ConstValue(i))
        End If
        With ThisDrawing
          .SetVariable cName, cValue 'ConstName(i), ConstValue(i) '
        End With
    Next i
    With ThisDrawing
         .SetVariable "DimLFac", dDimLFac   '线性比例因子. '1'=1:1, '2'=2:1,'.5'=1:2等
    End With
    
    dimStyle.CopyFrom ThisDrawing
'    DimLi.CopyFrom ThisDrawing

    With ThisDrawing '设置直径文字对齐方式为ISO方式，箭头及文字为优先移动箭头，尺寸线强制开
        .SetVariable "DIMTOH", 1
        .SetVariable "DIMTIH", 0
        .SetVariable "DIMATFIT", 1
        .SetVariable "DIMTOFL", 1
    End With
    DimDi.CopyFrom ThisDrawing
    With ThisDrawing '设置半径文字箭头为自动调整方式，箭头及文字自适应调整，尺寸线强制关
        .SetVariable "DIMTOH", 1
        .SetVariable "DIMTIH", 0
        .SetVariable "DIMATFIT", 3
        .SetVariable "DIMTOFL", 0
    End With
    DimRa.CopyFrom ThisDrawing

    With ThisDrawing '设置角度文字对齐方式为水平方式，尺寸线强制开
        .SetVariable "DIMTOH", 1
        .SetVariable "DIMTIH", 1
        .SetVariable "DIMATFIT", 3
        .SetVariable "DIMTOFL", 1
    End With
    DimAn.CopyFrom ThisDrawing

    ThisDrawing.ActiveDimStyle = dimStyle '激活该标注样式
    ThisDrawing.Regen acAllViewports
EEnd:
End Function

'------------------------------------------------------------------------------------------------------------------------------------------------------
'------------------------------------------------------------------------------------------------------------------------------------------------------
'将SW工程图转换的DWG图纸的基准标注符号补全并完善
'By Lee
'v1.0 2013-03-26
Public Sub MyDatum()
'    On Error Resume Next
    Dim mySet As AcadSelectionSet
    Dim Datum As AcadBlock
    Dim blin As AcadLine
    Dim tcir As AcadCircle
    Dim Dia As Double
    Dim aP1, aP2 As Variant
    Dim bP1, bP2 As Variant
    Dim intPts As Variant
    Dim txt, cir, lin As AcadEntity
'-----------------------------------------------------------------------------------------------------------
'此为手动选取基准标注块，但若是存在两个相同的
'基准标注块实例，则会存在重复添加基准线的情况
'    Set mySet = CtSS("mySet")
'    Dim Filtertype(0) As Integer, Filterdata(0) As Variant
'    Filtertype(0) = 2
'    Filterdata(0) = "*"
'    mySet.SelectOnScreen Filtertype, Filterdata
'
'    For Each Entry In mySet
'-----------------------------------------------------------------------------------------------------------
    For Each Entry In ThisDrawing.Blocks '此为全自动处理所有基准标注块
        If InStr(Entry.Name, "DATUM") > 0 Then '判断，若为基准标注块，则继续
            Set Datum = ThisDrawing.Blocks.Item(Entry.Name)
            For Each el In Datum 'ThisDrawing.Blocks.Item(Entry.Name)
                If el.ObjectName = "AcDbMText" Then
                    Set txt = el
                ElseIf el.ObjectName = "AcDbCircle" Then
                    Set cir = el
                ElseIf el.ObjectName = "AcDbLine" Then
                    If el.color = acWhite Then GoTo Done '有白色线说明已处理过，跳过不予重复处理
                    Set lin = el
                End If
            Next el
            '-------处理文字
            txt.color = acGreen
            txt.AttachmentPoint = acAttachmentPointMiddleCenter
            txt.InsertionPoint = cir.Center
            
            '-------添加基准线
            aP1 = cir.Center: bP1 = lin.StartPoint
            If P2PDistance(aP1, bP1) = cir.Diameter / 2 Then '如果startpoint在圆上，则ap1=endpoint,bp1=startpoint,否则，反之
                aP1 = lin.EndPoint
            Else
                aP1 = lin.StartPoint: bP1 = lin.EndPoint
            End If
            aP2 = RotatePAP2D(aP1, bP1, 90) '求基准线所在直线上两点，通过旋转直线端点的方式求得
            bP2 = RotatePAP2D(aP1, bP1, 270)
            Set blin = Datum.AddLine(aP2, bP2)
            Set tcir = Datum.AddCircle(aP1, cir.Diameter / 2)
            intPts = blin.IntersectWith(tcir, acExtendThisEntity) '求基准线与临时圆的交点
            aP2(0) = intPts(0): aP2(1) = intPts(1): aP2(2) = intPts(2)
            bP2(0) = intPts(3): bP2(1) = intPts(4): bP2(2) = intPts(5)
            blin.StartPoint = aP2: blin.EndPoint = bP2
            With blin
                .Layer = lin.Layer
                .color = acWhite
                .Linetype = "BYBLOCK"
                .Lineweight = acLnWtByBlock
            End With
            blin.Update
            tcir.Delete
        End If
Done:
    Next Entry
    ThisDrawing.Regen acAllViewports
End Sub

Public Function RotatePAP2D(bp As Variant, p1 As Variant, ang As Double) As Variant
    '计算p1点绕基准点bp旋转ang角度后的坐标，仅适用于二维坐标
    Dim p(0 To 2) As Double
    p(0) = (p1(0) - bp(0)) * Cos(ang / 180 * PI) - (p1(1) - bp(1)) * Sin(ang / 180 * PI) + bp(0)
    p(1) = (p1(0) - bp(0)) * Sin(ang / 180 * PI) - (p1(1) - bp(1)) * Cos(ang / 180 * PI) + bp(1)
    p(2) = 0
    RotatePAP2D = p
'    RotatePAP2D(0) = p(0): Set RotatePAP2D(1) = p(1): Set RotatePAP2D(2) = p(2)
End Function
Public Function CtSS(Optional ssName As String = "mySet") As AcadSelectionSet
    '返回一个空白选择集
    Dim SS As AcadSelectionSet

    On Error Resume Next
    Set SS = ThisDrawing.SelectionSets(ssName)
    If Err Then Set SS = ThisDrawing.SelectionSets.Add(ssName)
    SS.Clear
    Set CtSS = SS
End Function

Public Function FindFile(strFile As String)
'在autoCAD的当前目录、autoCAD目录及autoCAD的支持目录下查找所需的文件，如果找到文件，则返回文件的路径及文件名称，如不能找到文件，则返回空字符。
    Dim PrefFile As AcadPreferencesFiles
    Dim curSupportPath As String
    Dim numPath As Integer
    Dim strPath As String
    Dim pathName As String
    Dim PathTF As Boolean
    Dim SearchPath As String
    Dim appPath As String

    Set PrefFile = ThisDrawing.Application.Preferences.Files
    curSupportPath = PrefFile.SupportPath
    PathTF = True
    pathName = CurDir() & "\" & strFile '找当前图纸目录
    If Dir(pathName) = "" Then
        appPath = ThisDrawing.Application.Path
        pathName = appPath & "\" & strFile  '找cad安装路径
        
        If Dir(pathName) = "" Then
            Do While PathTF
                paths = Split(curSupportPath, ";")
                
                For Each p In paths '依次搜索每个支持路径
                    pathName = p & "\" & strFile
                                
                    'Debug.Print pathName
                
                    If Dir(pathName) <> "" Then
                        SearchPath = pathName
                        'MsgBox SearchPath
                        Exit Do
                    End If
                Next p
            Loop
        Else
            SearchPath = pathName
        End If
    Else
        SearchPath = pathName
    End If
    FindFile = SearchPath
End Function

Public Function P2PDistance(p1 As Variant, p2 As Variant) As Double
    '计算两点距离
    Dim dis As Double
    dis = Sqr((p1(0) - p2(0)) ^ 2 + (p1(1) - p2(1)) ^ 2 + (p1(2) - p2(2)) ^ 2)
    P2PDistance = dis
End Function

Attribute VB_Name = "Test"
Public Function test()

'    On Error Resume Next

    Dim TxtRow() As Variant, ConstName() As String, ConstValue() As String, SplitTxt() As String
    Dim L As Integer: L = -1
    Dim GBConstFileName As String
    Dim fso, sFile As Object
    
    GBConstFileName = FindFile("GBDimConst.txt")
    If GBConstFileName = "" Then MsgBox "没有找到GBDimConst.txt。请确认已将文件所在目录加入CAD支持的搜索路径。": GoTo EEnd
    Close #1: Open GBConstFileName For Input As #1
    Do Until EOF(1)
    L = L + 1
    ReDim Preserve ConstName(L), ConstValue(L), TxtRow(L)
    Line Input #1, TxtRow(L)
    ConstName(L) = Split(TxtRow(L), ";")(0)
    ConstValue(L) = Split(TxtRow(L), ";")(1)
    If InStr(ConstValue(L), "/*") > 0 Then ConstValue(L) = Split(ConstValue(L), "/*")(0)
    ConstName(L) = Replace(ConstName(L), vbTab, "")
    ConstValue(L) = Replace(ConstValue(L), vbTab, "")
    Loop
    Close #1
    Set fso = CreateObject("Scripting.FileSystemObject")
    
    
    Dim i As Integer, cName As String, cValue As Variant
    For i = 0 To UBound(ConstName)
        cName = CStr(ConstName(i))
        
        TxtRow(i) = ThisDrawing.GetVariable(cName)
        Set sFile = fso.opentextfile("D:\test.txt", 8, True)
        sFile.write cName & vbTab & ";" & TxtRow(i) & vbCrLf
        sFile.Close
    Next i
    Set fso = Nothing
    Set sFile = Nothing
EEnd:
End Function
Sub asb()
    MsgBox ThisDrawing.GetVariable("DIMADEC")
End Sub

Attribute VB_Name = "cusToolBar"
Option Explicit

'Dim testMacro As String
'Public Sub ACADStartup()
'    Call AcadApplication.RunMacro(".\AutoSWdwg.dvb!CreateVBAToolBar")
'End Sub
'Sub CreateVBAToolBar()
'    Dim objToolBars As AcadToolbars
'
'    Set objToolBars = ThisDrawing.Application.MenuGroups.Item(0).Toolbars
'
'    Dim objToolBar As AcadToolbar
'    On Error Resume Next
'    Set objToolBar = objToolBars.Add("VBA ToolBar")
'    If Err Then
'        Set objToolBar = objToolBars.Item("VBA ToolBar")
''       MsgBox "'VBA ToolBar' already exists!!"
'        Exit Sub
'    End If
'    On Error GoTo 0
'    Dim objToolbarItem As AcadToolbarItem
'    testMacro = Chr(3) + Chr(3) + "-vbarun" + Chr(32) + "ThisDrawing.AutoRun" + Chr(32)
'    Set objToolbarItem = objToolBar.AddToolbarButton(0, "Run Macro", "", testMacro)
'    Call objToolbarItem.SetBitmaps(".\Sample\VBA\VBAIDEmenu\vbarun.bmp", ".\Sample\VBA\VBAIDEmenu\vbarun.bmp")
'
'    Set objToolbarItem = objToolBar.AddToolbarButton(0, "Load Project", "Load Project", "_VBALOAD ")
'    Call objToolbarItem.SetBitmaps(".\Sample\VBA\VBAIDEmenu\vbaload.bmp", ".\Sample\VBA\VBAIDEmenu\vbaload.bmp")
'
'    Set objToolbarItem = objToolBar.AddToolbarButton(0, "VBA Manager", "VBA Manager", "_VBAMAN ")
'    Call objToolbarItem.SetBitmaps(".\Sample\VBA\VBAIDEmenu\vbaman.bmp", ".\Sample\VBA\VBAIDEmenu\vbaman.bmp")
'
'    Set objToolbarItem = objToolBar.AddToolbarButton(0, "VBA Options", "Invokes VBA Options Dialog", "_VBAPREF ")
'    Call objToolbarItem.SetBitmaps(".\Sample\VBA\VBAIDEmenu\vbaopt.bmp", ".\Sample\VBA\VBAIDEmenu\vbaopt.bmp")
''
'    Set objToolbarItem = objToolBar.AddToolbarButton(0, "VBA IDE", "VBA IDE", "_VBAIDE ")
'    Call objToolbarItem.SetBitmaps(".\Sample\VBA\VBAIDEmenu\vbaide.bmp", ".\Sample\VBA\VBAIDEmenu\vbaide.bmp")
'    objToolBar.Dock acToolbarDockRight
'    Call ThisDrawing.Application.MenuGroups.Item("ACAD").SaveAs("ACADVBA", acMenuFileSource)
'End Sub

Public Sub test()

Dim dimset As AcadSelectionSet
Dim el As Variant
Set dimset = CtSS("Dimset")

'Dim Filtertype(0 To 3) As Integer, Filterdata As Variant
'Filtertype(0) = -4: Filtertype(1) = 0: Filtertype(2) = 0: Filtertype(3) = -4
'Filterdata = Array("<OR", "Dimension", "Tolerance", "OR>")
dimset.SelectOnScreen 'Filtertype, Filterdata
For Each el In dimset
Next el

End Sub


Function GetVarType(var1 As Variant, var2 As Variant) As Variant
    Dim vv As Variant
    vv = ThisDrawing.GetVariable(var1)
    
    GetVarType = vv
End Function

Attribute VB_Name = "更新历史"

'当前版本:   v1 03
'更新日期:   2013-04-10






'==========================================================================================================================
'=====v1 03=====
'2013-04-10

'1.采用新的读取TXT配置文件方式设置尺寸样式
'2.修复了圆螺纹标注时出现“MΦ”的错误
'3.修复了公差标注后还有文字时，转换后公差跑到文字后的错误
'4.优化了新建标注样式命名

'=====v1 02=====
'2013-03-27

'1.添加形位公差支持，可更改形位公差为自定义标注样式；
'2.添加Solidworks图纸转换的基准标注的修正与完善；
'3.规范新建的国标标注样式，使其更符合平时使用习惯。

'=====v1 01=====
'2013-03-11

'修正下公差转化错误的问题。



'=====v1 00=====
'日期：2011.7

'第一版发布。主要具备以下功能：
'1.添加HZ字体样式（需CAD字库中存在HZTXT.shx文件），myDimStyle标注样式；
'2.转化所有文字为HZ字体样式；
'3.转化技术要求块多行文字；
'4.修正所有粗糙度符号，包括文字偏移纠正、规范线型；
'5.转化所选标注为自定义的标注样式；
'6.转化所选公差为字体替换方式显示，暂不支持转换形位公差

'--------------读取excel数据设置系统标注变量
'Public Sub test()
'    Dim ExcelApp As New Excel.Application
'    ExcelApp.Workbooks.Open "D:\CAD内置标注样式参数表.xls", , 1
'    Dim DimVar As String, DimValue As String
'    Dim mySheet As Variant
'    Set mySheet = ExcelApp.ActiveWorkbook.Worksheets("sheet1")
'    With mySheet
'        Dim i As Integer: i = 2
'        Do
'            With ThisDrawing
'                .SetVariable mySheet.Range("A" & i), mySheet.Range("D" & i)
'            End With
'        Loop While (.Range("A" & i + 1) = "")
'    End With
'
'End Sub
