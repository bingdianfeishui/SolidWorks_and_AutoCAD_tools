Attribute VB_Name = "ModifyTittleBlock"
Public Sub main()
    UserForm.Show
    
End Sub







Public Sub test()
    

End Sub











Public Function ReplaceText(oldText As String, newText As String)
     For Each entry In ThisDrawing.Blocks
        If InStr(entry.Name, "FitPDM_DWGFrame") > 0 Then
            For Each element In entry
                If (element.ObjectName = "AcDbText") Then
                    ThisDrawing.Utility.Prompt "找到文本：" & element.TextString
                    If (element.TextString = oldText) Then
                        element.TextString = newText
                        ThisDrawing.Utility.Prompt "[" & oldText & "]被替换为[" & newText
                    End If
                End If
            Next element
            
            ThisDrawing.Regen acAllViewports
            Exit For
        End If
    Next entry
End Function
    
'Sub Example_Limits()
'    ' This example finds the current limits for the drawing.
'    ' It then changes the limits for the drawing. The grid
'    ' is turned on to show the limits.
'
'    ' Turn on the grid for the active viewport
'    Dim grid As Boolean
'
''    grid = ThisDrawing.ActiveViewport.GridOn
'    ThisDrawing.ActiveViewport = ThisDrawing.ActiveViewport
'
'    ' Find the current limits
'    Dim currLimits As Variant
'
'    currLimits = ThisDrawing.Limits
'    ThisDrawing.Utility.Prompt "The current drawing limits are " & vbCrLf _
'           & "Lower-left corner " & ThisDrawing.Limits(0) & ", " & ThisDrawing.Limits(1) & vbCrLf _
'           & "Upper-right corner " & ThisDrawing.Limits(2) & ", " & ThisDrawing.Limits(3)
'
'    ' Change the limits
'    Dim newLimits(0 To 3) As Double
'
'    newLimits(0) = 2#: newLimits(1) = 2#: newLimits(2) = 400#: newLimits(3) = 400#
'    ThisDrawing.Limits = newLimits
'    ThisDrawing.Regen acActiveViewport
'    ThisDrawing.Utility.Prompt "The new drawing limits are " & vbCrLf _
'           & "Lower-left corner " & ThisDrawing.Limits(0) & ", " & ThisDrawing.Limits(1) & vbCrLf _
'           & "Upper-right corner " & ThisDrawing.Limits(2) & ", " & ThisDrawing.Limits(3)
'
'
'    ' Reset the drawing limits
'    ThisDrawing.Limits = currLimits
'    ThisDrawing.Regen acActiveViewport
'    ThisDrawing.Utility.Prompt "The drawing limits have been reset to " & vbCrLf _
'           & "Lower-left corner " & ThisDrawing.Limits(0) & ", " & ThisDrawing.Limits(1) & vbCrLf _
'           & "Upper-right corner " & ThisDrawing.Limits(2) & ", " & ThisDrawing.Limits(3)
'
'
'
'End Sub

Attribute VB_Name = "UserForm"
Attribute VB_Base = "0{BE3835BF-9F13-4D41-8E8A-84C4615E8498}{9E04891B-4100-43CE-A323-660D3E7E6492}"
Attribute VB_GlobalNameSpace = False
Attribute VB_Creatable = False
Attribute VB_PredeclaredId = True
Attribute VB_Exposed = False
Attribute VB_TemplateDerived = False
Attribute VB_Customizable = False


Dim pageRec(4) As Variant
Dim tittleBlock As Object
Dim sSet As AcadSelectionSet
Dim areaPt1(2) As Double
Dim areaPt2(2) As Double

Dim 图号区域        As Variant
Dim 图纸名称区域    As Variant
Dim 图标区域        As Variant
Dim 版本区域        As Variant
Dim 重量区域        As Variant
Dim 比例区域        As Variant
Dim 总张数区域      As Variant
Dim 张数区域        As Variant
Dim 密级区域        As Variant
Dim 图号区域左上    As Variant

Dim dwgInfoText(1 To 10) As Variant

Private Sub OptionButton1_Click()

End Sub

Private Sub optNormal_Click()

End Sub

Private Sub UserForm_Initialize()
    
    Call getPageRec
'    Call markArea

    ' 获取图纸信息区域
    图号区域 = getRec(1)
    图纸名称区域 = getRec(2)
    图标区域 = getRec(3)
    版本区域 = getRec(4)
    重量区域 = getRec(5)
    比例区域 = getRec(6)
    总张数区域 = getRec(7)
    张数区域 = getRec(8)
    密级区域 = getRec(9)
    图号区域左上 = getRec(10)
    
    If isTittleExploded() Then
        ' 获取图纸区域内的信息文字
        getTextElement 图号区域, 1
        getTextElement 图纸名称区域, 2
        getTextElement 版本区域, 4
        getTextElement 重量区域, 5
        getTextElement 比例区域, 6
        getTextElement 总张数区域, 7
        getTextElement 张数区域, 8
        getTextElement 密级区域, 9
        getTextElement 图号区域左上, 10
        
        If Not IsNull(dwgInfoText(1)) Then txtDwgNO.Text = dwgInfoText(1).TextString
        If Not IsNull(dwgInfoText(2)) Then txtDwgName.Text = dwgInfoText(2).TextString
        If Not IsNull(dwgInfoText(4)) Then txtVersion.Text = dwgInfoText(4).TextString
        If Not IsNull(dwgInfoText(5)) Then txtWeight.Text = dwgInfoText(5).TextString
        If Not IsNull(dwgInfoText(6)) Then txtScale.Text = dwgInfoText(6).TextString
        If Not IsNull(dwgInfoText(7)) Then txtTotalPages.Text = dwgInfoText(7).TextString
        If Not IsNull(dwgInfoText(8)) Then txtPage.Text = dwgInfoText(8).TextString
        If Not IsNull(dwgInfoText(9)) Then
            If StrComp(dwgInfoText(9).TextString, "核心机密") = 0 Then
                optNormal.Value = False
                optSecret.Value = True
            Else 'If StrComp(dwgInfoText(9).TextString, "普通商密") = 0 Then
                optNormal.Value = True
                optSecret.Value = False
            End If
        End If
        If Not IsNull(dwgInfoText(10)) Then printMsg dwgInfoText(10).TextString
    End If

    
    
'    Call testBlock
    
    
End Sub

' 判断图框是否被炸开
Function isTittleExploded()
    Dim fType(1) As Integer
    Dim fData(1) As Variant
    fType(0) = 0
    fType(1) = 1
    fData(0) = "Text"
    fData(1) = "PLM控制 涂改无效"
    Call getSSet
    sSet.Select acSelectionSetAll, , , fType, fData
    isTittleExploded = (Not IsEmpty(sSet))
End Function

Public Sub testBlock1()
    Dim blk As AcadBlock
    Set blk = ThisDrawing.Blocks.Item("FitPDM_DWGFrame")
    For Each entity In blk
        printMsg entity.Name & ", " & entity.ObjectName & ", " & entity.EntityName
    Next entity
End Sub
Public Sub testBlock()
    Dim fType(1) As Integer
    Dim fData(1) As Variant
    fType(0) = 0
    fType(1) = 2
    fData(0) = "*"
    fData(1) = "FitPDM_DWGFrame"
    Call getSSet
    areaPt1(0) = 0
    areaPt1(1) = 0
    areaPt1(2) = 0
    areaPt2(0) = 297
    areaPt2(1) = 210
    areaPt1(2) = 0
    sSet.Select acSelectionSetAll, , , fType, fData
    For Each entity In sSet
        printMsg entity.Name & ", " & entity.ObjectName & ", " & entity.EntityName
    Next entity
End Sub


Function getAreaPts(ByVal rec As Variant)
    areaPt1(0) = rec(0)
    areaPt1(1) = rec(1)
    areaPt1(2) = 0
    areaPt2(0) = rec(2)
    areaPt2(1) = rec(3)
    areaPt1(2) = 0
End Function

Function getSSet()
    ssName = "SelectionSetDemo"
    On Error Resume Next
    Set sSet = ThisDrawing.SelectionSets(ssName)
    If Err Then Set sSet = ThisDrawing.SelectionSets.Add(ssName)
    sSet.Clear
    'getSSet = sSet
End Function

Function getTextElement(ByVal rec As Variant, ByVal txtIndex As Integer)
    Dim fType(0) As Integer
    Dim fData(0) As Variant
    
    ' 根据rec坐标获取选择集范围的端点
    getAreaPts rec
    
    fType(0) = 0    '第一组，过滤图元
    fData(0) = "text" '过滤类型：文字
    Call getSSet
    sSet.Select acSelectionSetWindow, areaPt1, areaPt2, fType, fData
    printMsg "选择集内元素数量" & sSet.Count
    If sSet.Count = 1 Then
        Set dwgInfoText(txtIndex) = sSet.Item(0)
    ElseIf sSet.Count > 1 Then
        Set dwgInfoText(txtIndex) = sSet.Item(0)
    End If
End Function

''===========================================
''                  获取文字对象
''===========================================
'Function getDwgNO(ByVal rec As Variant)
'    Dim txt As AcadText
'    Set txt = getTextElement(rec, txtDwgNO)
'    If Not IsEmpty(txt) Then
'        txtDwgNO.Text = txt.TextString
'        Set getDwgNO = txt
'        Exit Function
'    End If
'    Set getDwgNO = Null
'End Function
'
'Function getDwgName(ByVal rec As Variant)
'    Dim txt As AcadText
'    Set txt = getTextElement(rec)
'    If Not IsNull(txt) Then
'        txtDwgName.Text = txt.TextString
'        Set getDwgName = txt
'        Exit Function
'    End If
'    Set getDwgName = Null
'End Function
'
'Function getDwgVersion(ByVal rec As Variant)
'    Dim txt As AcadText
'    Set txt = getTextElement(rec)
'    If Not IsNull(txt) Then
'        txtVersion.Text = txt.TextString
'        Set getDwgVersion = txt
'        Exit Function
'    End If
'    Set getDwgVersion = Null
'End Function
'
'Function getDwgWeight(ByVal rec As Variant)
'    Dim txt As AcadText
'    Set txt = getTextElement(rec)
'    If Not IsNull(txt) Then
'        txtWeight.Text = txt.TextString
'        Set getDwgWeight = txt
'        Exit Function
'    End If
'    Set getDwgWeight = Null
'End Function
'
'Function getDwgScale(ByVal rec As Variant)
'    Dim txt As AcadText
'    Set txt = getTextElement(rec)
'    If Not IsNull(txt) Then
'        txtScale.Text = txt.TextString
'        Set getDwgScale = txt
'        Exit Function
'    End If
'    Set getDwgScale = Null
'End Function
'
'Function getTotalPages(ByVal rec As Variant)
'
'End Function
'
'Function getDwgPage(ByVal rec As Variant)
'
'End Function
'Function getSecret(ByVal rec As Variant)
'
'End Function
'Function getDwgNO2(ByVal rec As Variant)
'
'End Function

Private Sub btnModify_Click()
    'Call ReplaceText(TextBoxOld.Text, TextBoxNew.Text)
    updateDwgInfo
    

    updateLogo

    ThisDrawing.Regen acAllViewports
End Sub

Function updateDwgInfo()
    If Not IsNull(dwgInfoText(1)) Then dwgInfoText(1).TextString = txtDwgNO.Text
    If Not IsNull(dwgInfoText(2)) Then dwgInfoText(2).TextString = txtDwgName.Text
    If Not IsNull(dwgInfoText(4)) Then dwgInfoText(4).TextString = txtVersion.Text
    If Not IsNull(dwgInfoText(5)) Then dwgInfoText(5).TextString = txtWeight.Text
    If Not IsNull(dwgInfoText(6)) Then dwgInfoText(6).TextString = txtScale.Text
    If Not IsNull(dwgInfoText(7)) Then dwgInfoText(7).TextString = txtTotalPages.Text
    If Not IsNull(dwgInfoText(8)) Then dwgInfoText(8).TextString = txtPage.Text
    If Not IsNull(dwgInfoText(9)) Then
        If optNormal.Value Then
            dwgInfoText(9).TextString = "普通商密"
        Else 'If StrComp(dwgInfoText(9).TextString, "普通商密") = 0 Then
            dwgInfoText(9).TextString = "核心机密"
        End If
    End If
    If Not IsNull(dwgInfoText(10)) Then dwgInfoText(10).TextString = txtDwgNO.Text
End Function

Function updateLogo()

    ' 删除原来的旧logo
    Dim fType(0) As Integer
    Dim fData(0) As Variant
    
    ' 根据rec坐标获取选择集范围的端点
    getAreaPts 图标区域
    
    fType(0) = 0    '第一组，过滤图元
    fData(0) = "*" '过滤类型：文字
    Call getSSet
    sSet.Select acSelectionSetWindow, areaPt1, areaPt2, fType, fData
    printMsg "选择集内元素数量" & sSet.Count
    For Each entity In sSet
        entity.Delete
    Next entity


    vbaPath = GetVBAFilePath
    
    Dim insertionPnt(0 To 2) As Double
    Dim blockRefObj As AcadBlockReference

    insertionPnt(0) = areaPt1(0)
    insertionPnt(1) = areaPt1(1)
    insertionPnt(2) = 0
    Set blockRefObj = ThisDrawing.ModelSpace.InsertBlock(insertionPnt, vbaPath & "logo.dwg", 1#, 1#, 1#, 0)

End Function

Public Function GetVBAFilePath() As String
    Dim strFileName
    strFileName = VBE.ActiveVBProject.FileName 'VBE.ActiveVBProject.FileName获取.dvb文件的文件名
    GetVBAFilePath = Left$(strFileName, InStrRev(strFileName, "\"))
End Function
Function markArea()
    Dim rec As Variant
    For i = 1 To 8
        rec = getRec(i)
        drawLine rec
    Next i
    rec = getRec(101)
        drawLine rec
        rec = getRec(102)
        drawLine rec
End Function

'获取图幅，存储到pageRec全局变量中
Function getPageRec()
    On Error Resume Next
    
    '先尝试选择标题框
    Dim minPt, maxPt As Variant
    Dim fType(0) As Integer
    Dim fData(0) As Variant
    fType(0) = 0    '过滤图元
    fData(0) = "Insert" '过滤类型：图块
    Call getSSet
    sSet.Select acSelectionSetAll, , , fType, fData
    Debug.Print "选择集内元素数量" & sSet.Count
    If (sSet.Count > 0) Then
        For Each blkref In sSet
            If StrComp(blkref.Name, "FitPDM_DWGFrame") = 0 Then
                tittleBlock = blkref
                blkref.GetBoundingBox minPt, maxPt  '获取图块的包络外边框
                
                Exit For
            End If
        Next blkref
    End If

    
    '未找到图框顶点，则提示用户选择
    If IsEmpty(minPt(0)) Then
        printMsg "未找到图框，请手动选择图框顶点。"
'        Me.Hide
        minPt = ThisDrawing.Utility.GetPoint(, "请选择左下角顶点：")
        If Not IsEmpty(minPt) Then
            maxPt = ThisDrawing.Utility.GetPoint(, "请选择右上角顶点：")
        End If
'        Me.Show
    End If
    
    If (IsEmpty(minPt) Or IsEmpty(maxPt)) Then
        printMsg "Error: 图框顶点选择有误!!"
        getPageRec = False
        Exit Function
    End If
    
    
    pageRec(0) = minPt(0)
    pageRec(1) = minPt(1)
    pageRec(2) = maxPt(0)
    pageRec(3) = maxPt(1)
    
    printMsg "找到图框边界点: (" & pageRec(0) & ", " & pageRec(1) & ") (" & pageRec(2) & ", " & pageRec(3) & ")"

    getPageRec = True
'    '未找到标题框，则采用Limits方案
'    Dim grid As Boolean
'    Dim currLimits As Variant
'
'    grid = ThisDrawing.ActiveViewport.GridOn
'    ThisDrawing.ActiveViewport.GridOn = True
'    ThisDrawing.ActiveViewport = ThisDrawing.ActiveViewport
'
'    ' Find the current limits
'    currLimits = ThisDrawing.Limits
'    printMsg "The current drawing limits are " & vbCrLf _
'           & "Lower-left corner " & ThisDrawing.Limits(0) & ", " & ThisDrawing.Limits(1) & vbCrLf _
'           & "Upper-right corner " & ThisDrawing.Limits(2) & ", " & ThisDrawing.Limits(3)
'
'    ThisDrawing.ActiveViewport.GridOn = grid

'ErrTrap:
'    ' 防止出错时窗体不显示
'    Me.Show
'    On Error GoTo 0
End Function


Function printMsg(ByVal msg As Variant)
    ThisDrawing.Utility.Prompt msg & vbCrLf
End Function

Function getRec(ByVal index As Integer)
    Dim rec(3) As Variant
    Dim blank As Integer '图框空白边缘的宽度
    
    If Math.Abs(pageRec(0) - pageRec(2)) > 297 Or Math.Abs(pageRec(1) - pageRec(3)) > 297 Then
        blank = 10
    Else
        blank = 5
    End If
    
    Select Case index
    
        
        '===============标题栏==============
        
        Case 1  '图号区域
            rec(0) = pageRec(2) - 60 - blank
            rec(1) = pageRec(1) + 48 + blank
            rec(2) = pageRec(2) - blank
            rec(3) = pageRec(1) + 68 + blank
        Case 2  '图纸名称区域
            rec(0) = pageRec(2) - 118 - blank
            rec(1) = pageRec(1) + 20 + blank
            rec(2) = pageRec(2) - 60 - blank
            rec(3) = pageRec(1) + 68 + blank
        Case 3  '图标区域
            rec(0) = pageRec(2) - 60 - blank
            rec(1) = pageRec(1) + blank
            rec(2) = pageRec(2) - blank
            rec(3) = pageRec(1) + 20 + blank
        '未校对
        Case 4  '版本区域
            rec(0) = pageRec(2) - 60 - blank
            rec(1) = pageRec(1) + 28 + blank
            rec(2) = pageRec(2) - 40 - blank
            rec(3) = pageRec(1) + 40 + blank
        Case 5  '重量区域
            rec(0) = pageRec(2) - 40 - blank
            rec(1) = pageRec(1) + 28 + blank
            rec(2) = pageRec(2) - 20 - blank
            rec(3) = pageRec(1) + 40 + blank
        Case 6  '比例区域
            rec(0) = pageRec(2) - 20 - blank
            rec(1) = pageRec(1) + 28 + blank
            rec(2) = pageRec(2) - blank
            rec(3) = pageRec(1) + 40 + blank
        Case 7  '总张数区域
            rec(0) = pageRec(2) - 60 - blank
            rec(1) = pageRec(1) + 20 + blank
            rec(2) = pageRec(2) - 30 - blank
            rec(3) = pageRec(1) + 28 + blank
        Case 8  '张数区域
            rec(0) = pageRec(2) - 30 - blank
            rec(1) = pageRec(1) + 20 + blank
            rec(2) = pageRec(2) - blank
            rec(3) = pageRec(1) + 28 + blank
        
        '===============左上角角标==============
        Case 9  '密级区域
            rec(0) = pageRec(0) + 80
            rec(1) = pageRec(3) - 15 - blank
            rec(2) = pageRec(0) + 125
            rec(3) = pageRec(3) - blank
        Case 10  '图号区域左上
            rec(0) = pageRec(0) + 25
            rec(1) = pageRec(3) - 15 - blank
            rec(2) = pageRec(0) + 70
            rec(3) = pageRec(3) - blank
    End Select
    getRec = rec
End Function


Function drawLine(ByVal cd As Variant)
    Dim pt0(2) As Double
    Dim pt1(2) As Double
    Dim line As AcadLine
    pt0(0) = cd(0)
    pt0(1) = cd(1)
    pt0(2) = 0
    pt1(0) = cd(2)
    pt1(1) = cd(3)
    pt0(2) = 0
    
    Set line = ThisDrawing.ModelSpace.AddLine(pt0, pt1)
    ZoomAll
End Function


'    For Each Entry In ThisDrawing.Blocks
'        If StrComp(Entry.Name, "FitPDM_DWGFrame") = 0 Then
'            For Each element In Entry
'                If element.ObjectName = "AcDbText" Then
'                    ThisDrawing.Utility.Prompt element.TextString & "   "
'                    If element.TextString = "公司秘密" Then
'                        element.TextString = "普通商密"
'                    End If
'
'                End If
'            Next element
'        End If
'    Next Entry




Private Sub UserForm_Terminate()
    If Not IsEmpty(sSet) Then
        sSet.Delete
    End If
End Sub
